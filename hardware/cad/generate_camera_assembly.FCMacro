from pathlib import Path
import os
import subprocess
import sys

import FreeCAD as App
import MeshPart
import Part

ROOT = Path(__file__).resolve().parents[2]
BOARD_STEP = ROOT / "tmp" / "manufacturing" / "rpi-camera-led-board.step"
PCB = ROOT / "hardware" / "rpi-camera-led.kicad_pcb"
OUT = ROOT / "tmp" / "cad"
OUT.mkdir(parents=True, exist_ok=True)
STEP_DIR = OUT / "components"
STEP_DIR.mkdir(parents=True, exist_ok=True)

sys.path.insert(0, str(ROOT / "hardware" / "tools"))
from kicad_cli import KICAD_CLI

model_dirs = [
    os.environ.get("KICAD10_3DMODEL_DIR"),
    os.environ.get("KICAD9_3DMODEL_DIR"),
    str(Path(KICAD_CLI).resolve().parent.parent / "share" / "kicad" / "3dmodels"),
    "/usr/share/kicad/3dmodels",
    "/snap/kicad/current/share/kicad/3dmodels",
    "/Applications/KiCad/KiCad.app/Contents/SharedSupport/3dmodels",
]
model_dir = next((path for path in model_dirs if path and Path(path).is_dir()), None)
if model_dir is None:
    raise FileNotFoundError(f"KiCad STEP model directory not found: {model_dir}")

component_groups = {
    "Connectors": "J1,J2,J3,J4",
    "IC": "U1",
    "LEDs": "D1,D2",
    "Sensor": "Q2",
    "MOSFET": "Q1",
    "Passives": "C1,C2,R1,R2,R3,R4,R5,R6,R7,R8,R9",
}

doc = App.newDocument("RpiCameraLedAssembly")
board_shape = Part.read(str(BOARD_STEP))
board_outline_shape = Part.read(str(BOARD_STEP))
board_box = board_outline_shape.BoundBox
print("Interposer board substrate bounds:", board_box)

interposer = doc.addObject("PartDesign::Feature", "Interposer")
interposer.Label = "RPI Camera LED interposer (KiCad STEP)"
interposer.Shape = board_shape
component_objects = []
for category, references in component_groups.items():
    component_step = STEP_DIR / f"{category}.step"
    subprocess.run(
        [
            KICAD_CLI,
            "pcb",
            "export",
            "step",
            "--force",
            "--component-filter",
            references,
            "--define-var",
            f"KICAD9_3DMODEL_DIR={model_dir}",
            "--define-var",
            f"KICAD10_3DMODEL_DIR={model_dir}",
            "-o",
            str(component_step),
            str(PCB),
        ],
        check=True,
    )
    exported = Part.read(str(component_step))
    parts = []
    for child in exported.childShapes():
        box = child.BoundBox
        if (
            abs(box.XLength - board_box.XLength) < 0.01
            and abs(box.YLength - board_box.YLength) < 0.01
            and abs(box.ZLength - board_box.ZLength) < 0.01
        ):
            continue
        parts.append(child)
    if not parts:
        raise RuntimeError(f"KiCad exported no component geometry for {category}")
    component = doc.addObject("PartDesign::Feature", f"Components{category}")
    component.Label = f"Populated components: {category}"
    component.Shape = Part.makeCompound(parts)
    component_objects.append(component)

board_bottom = board_box.ZMin
camera_top = board_bottom - 5.0
camera_thickness = 1.12
camera_bottom = camera_top - camera_thickness
cx, cy = 32.5, -25.681
camera_outline_width, camera_outline_height = 25.0, 23.862
camera_left, camera_top_edge = 20.0, -16.319
camera_bottom_edge = camera_top_edge - camera_outline_height
holes = [(22.0, -25.681), (43.0, -25.681),
         (22.0, -38.181), (43.0, -38.181)]

camera_plate = Part.makeBox(
    camera_outline_width,
    camera_outline_height,
    camera_thickness,
    App.Vector(camera_left, camera_bottom_edge, camera_bottom),
)
vertical_edges = [
    edge for edge in camera_plate.Edges
    if edge.BoundBox.ZLength > camera_thickness - 0.01
]
camera_plate = camera_plate.makeFillet(1.5, vertical_edges)
for x, y in holes:
    bore = Part.makeCylinder(
        1.1, camera_thickness + 0.2, App.Vector(x, y, camera_bottom - 0.1)
    )
    camera_plate = camera_plate.cut(bore)
camera = doc.addObject("PartDesign::Feature", "CameraModule")
camera.Label = "Camera Module 3 Standard PCB (25 x 23.862 x 1.12 mm)"
camera.Shape = camera_plate

actuator = doc.addObject("PartDesign::Feature", "AutofocusActuator")
actuator.Label = "Camera Module 3 autofocus actuator envelope (10.8 mm square)"
actuator.Shape = Part.makeBox(
    10.8, 10.8, 3.875,
    App.Vector(cx - 5.4, cy - 5.4, camera_top),
)

lens_holder = doc.addObject("PartDesign::Feature", "LensHolder")
lens_holder.Label = "Camera Module 3 AF lens barrel envelope (OD 5.75 mm)"
lens_holder.Shape = Part.makeCylinder(
    2.875, 6.98, App.Vector(cx, cy, camera_top + 3.875)
)

lens_glass = doc.addObject("PartDesign::Feature", "LensGlass")
lens_glass.Label = "Camera Module 3 AF front lens plane (approximate)"
lens_glass.Shape = Part.makeCylinder(
    2.65, 0.25, App.Vector(cx, cy, camera_top + 10.855)
)

camera_connector = doc.addObject("PartDesign::Feature", "CameraFFCConnector")
camera_connector.Label = "Camera Module 3 FFC connector envelope (approximate)"
camera_connector.Shape = Part.makeBox(
    8.9, 3.3, 1.8,
    App.Vector(14.4, camera_bottom_edge - 3.3, camera_bottom - 1.8),
)

for index, (x, y) in enumerate(holes, 1):
    spacer_shape = Part.makeCylinder(1.6, 5.0, App.Vector(x, y, camera_top)).cut(
        Part.makeCylinder(1.1, 5.2, App.Vector(x, y, camera_top - 0.1))
    )
    spacer = doc.addObject("PartDesign::Feature", f"Spacer{index}")
    spacer.Label = f"M2 camera standoff {index} (approximate)"
    spacer.Shape = spacer_shape

camera_cable = doc.addObject("PartDesign::Feature", "CameraFFC")
camera_cable.Label = "Camera Module 3 FFC stub (illustrative)"
camera_cable.Shape = Part.makeBox(
    15.0, 9.0, 0.3,
    App.Vector(18.85 - 7.5, camera_bottom_edge - 12.3, camera_bottom - 2.1),
)

pi_cable = doc.addObject("PartDesign::Feature", "PiFFC")
pi_cable.Label = "Raspberry Pi FFC path (illustrative)"
pi_cable.Shape = Part.makeBox(
    12.0, 15.0, 0.35, App.Vector(-2.5, cy - 7.5, board_bottom + 1.8)
)

doc.recompute()
doc.saveAs(str(OUT / "rpi-camera-led-assembly.FCStd"))
Part.export(
    [interposer, *component_objects, camera, actuator, lens_holder, lens_glass,
     camera_connector]
    + [doc.getObject(f"Spacer{i}") for i in range(1, 5)]
    + [camera_cable, pi_cable],
    str(OUT / "rpi-camera-led-assembly.step"),
)

objects = [
    interposer, *component_objects, camera, actuator, lens_holder, lens_glass,
    camera_connector,
    *[doc.getObject(f"Spacer{i}") for i in range(1, 5)],
    camera_cable, pi_cable,
]
for obj in objects:
    mesh = MeshPart.meshFromShape(
        Shape=obj.Shape, LinearDeflection=0.08, AngularDeflection=0.15,
        Relative=False,
    )
    mesh.write(str(OUT / f"{obj.Name}.stl"))

print("Assembly written to", OUT)
App.closeDocument(doc.Name)
